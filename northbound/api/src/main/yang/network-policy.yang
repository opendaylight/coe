module network-policy {
    yang-version 1;
    namespace "urn:opendaylight:coe:northbound:network-policy";
    prefix "network-policy";

    description
        "This YANG module defines the kubernetes network policy API.";

    revision "2018-12-05" {
        description "Initial revision.";
    }

    import ietf-yang-types { prefix yang; revision-date "2013-07-15"; }
    import core { prefix core; revision-date "2018-12-05"; }
    import meta-v1 { prefix meta-v1; revision-date "2018-12-05"; }

    organization "OpenDaylight COE Group";

    contact "COE Developers <coe-dev@lists.opendaylight.org>";

    typedef policy-type {
        description "List of rule types that the NetworkPolicy relates to.";
        type enumeration {
            enum "egress";
            enum "ingress";
        }
    }

    grouping ip-block {
        description
            "IPBlock describes a particular CIDR (Ex. \"192.168.1.1/24\") that
             is allowed to the pods matched by a NetworkPolicySpec's
             podSelector. The except entry describes CIDRs that should
             not be included within this rule.";

        leaf cidr {
            description
                "CIDR is a string representing the IP Block
                 Valid examples are \"192.168.1.1/24\"";

            type string;

            mandatory true;
        }

        leaf-list except {
            description
                "Except is a slice of CIDRs that should not be included within
                 an IP Block. Valid examples are \"192.168.1.1/24\". Except
                 values will be rejected if they are outside the CIDR range.";

            type string;
        }
    }

    grouping network-policy-peer {
        description
            "NetworkPolicyPeer describes a peer to allow traffic from.";

        container pod-selector {
            description
                "This is a label selector which selects Pods. This field
                 follows standard label selector semantics; if present but
                 empty, it selects all pods. If NamespaceSelector is also set,
                 then the NetworkPolicyPeer as a whole selects the Pods
                 matching PodSelector in the Namespaces selected by
                 NamespaceSelector. Otherwise it selects the Pods matching
                 PodSelector in the policy's own Namespace.";

            uses meta-v1:label-selector;
        }

        container namespace-selector {
            description
                "Selects Namespaces using cluster-scoped labels. This field
                 follows standard label selector semantics; if present but
                 empty, it selects all namespaces. If PodSelector is also set,
                 then the NetworkPolicyPeer as a whole selects the Pods
                 matching PodSelector in the Namespaces selected by
                 NamespaceSelector. Otherwise it selects all Pods in the
                 Namespaces selected by NamespaceSelector.";

            uses meta-v1:label-selector;
        }

        container ip-block {
            description
                "IPBlock defines policy on a particular IPBlock. If this field
                 is set then neither of the other fields can be.";

            uses ip-block;
        }
    }

    grouping network-policy-port {
        description
            "NetworkPolicyPort describes a port to allow traffic on";

        leaf protocol {
            description
                "The protocol (TCP, UDP, or SCTP) which traffic must match.
                 If not specified, this field defaults to TCP.";

            type core:protocol;
        }

        leaf port {
            description
                "The port on the given protocol. This can either be a
                 numerical or named port on a pod. If this field is not
                 provided, this matches all port names and numbers.";

            type string;
        }
    }

    grouping network-policy-ingress-rule {
        description
            "NetworkPolicyIngressRule describes a particular set of traffic
             that is allowed to the pods matched by a NetworkPolicySpec's
             podSelector. The traffic must match both ports and from.";

        list ports {
            description
                "List of ports which should be made accessible on the pods
                 selected for this rule. Each item in this list is combined
                 using a logical OR. If this field is empty or missing, this
                 rule matches all ports (traffic not restricted by port). If
                 this field is present and contains at least one item, then
                 this rule allows traffic only if the traffic matches at least
                 one port in the list.";

            uses network-policy-port;
        }

        list from {
            description
                "List of sources which should be able to access the pods
                 selected for this rule. Items in this list are combined using
                 a logical OR operation. If this field is empty or missing,
                 this rule matches all sources (traffic not restricted by
                 source). If this field is present and contains at least on
                 item, this rule allows traffic only if the traffic matches
                 at least one item in the from list.";

            uses network-policy-peer;
        }
    }

    grouping network-policy-egress-rule {
        description
            "NetworkPolicyEgressRule describes a particular set of traffic
             that is allowed out of pods matched by a NetworkPolicySpec's
             podSelector. The traffic must match both ports and to.";

        list ports {
            description
                "List of destination ports for outgoing traffic.
                 Each item in this list is combined using a logical OR. If
                 this field is empty or missing, this rule matches all ports
                 (traffic not restricted by port). If this field is present
                 and contains at least one item, then this rule allows traffic
                 only if the traffic matches at least one port in the list.";

            uses network-policy-port;
        }

        list to {
            description
                "List of destinations for outgoing traffic of pods selected
                 for this rule. Items in this list are combined using a
                 logical OR operation. If this field is empty or missing, this
                 rule matches all destinations (traffic not restricted by
                 destination). If this field is present and contains at least
                 one item, this rule allows traffic only if the traffic
                 matches at least one item in the to list.";

            uses network-policy-peer;
        }
    }

    grouping network-policy-spec {
        description
            "NetworkPolicySpec provides the specification of a
             NetworkPolicy.";

        container pod-selector {
            description
                "Selects the pods to which this NetworkPolicy object applies. The
                 array of ingress rules is applied to any pods selected by this
                 field. Multiple network policies can select the same set of pods.
                 In this case, the ingress rules for each are combined additively.
                 This field is NOT optional and follows standard label selector
                 semantics. An empty podSelector matches all pods in this
                 namespace.";

            uses meta-v1:label-selector;
        }

        list ingress {
            description
                "List of ingress rules to be applied to the selected pods.
                 Traffic is allowed to a pod if there are no NetworkPolicies
                 selecting the pod (and cluster policy otherwise allows the
                 traffic), OR if the traffic source is the pod's local node,
                 OR if the traffic matches at least one ingress rule across
                 all of the NetworkPolicy objects whose podSelector matches
                 the pod. If this field is empty then this NetworkPolicy does
                 not allow any traffic (and serves solely to ensure that the
                 pods it selects are isolated by default)";
            uses network-policy-ingress-rule;
        }

        list egress {
            description
                "List of egress rules to be applied to the selected pods.
                 Outgoing traffic is allowed if there are no NetworkPolicies
                 selecting the pod (and cluster policy otherwise allows the
                 traffic), OR if the traffic matches at least one egress rule
                 across all of the NetworkPolicy objects whose podSelector
                 matches the pod. If this field is empty then this
                 NetworkPolicy limits all outgoing traffic (and serves solely
                 to ensure that the pods it selects are isolated by
                 default).";

            uses network-policy-egress-rule;
        }

        leaf-list policy-types {
            description
                "List of rule types that the NetworkPolicy relates to.
                 Valid options are Ingress, Egress, or Ingress,Egress.
                 If this field is not specified, it will default based on the
                 existence of Ingress or Egress rules; policies that contain
                 an Egress section are assumed to affect Egress, and all
                 policies (whether or not they contain an Ingress section) are
                 assumed to affect Ingress. If you want to write an
                 egress-only policy, you must explicitly specify policyTypes
                 [ Egress ]. Likewise, if you want to write a policy that
                 specifies that no egress is allowed, you must specify a
                 policyTypes value that include \"Egress\" (since such a policy
                 would not include an Egress section and would otherwise
                 default to just [ \"Ingress\" ]).";

            type policy-type;
        }
    }

    container network-policy {
        description
            "NetworkPolicyList is a list of NetworkPolicy objects.";

        list network-policy {
            key "uuid";

            leaf uuid {
                type yang:uuid;
                description "UUID representing the network-policy.";
            }

            uses network-policy-spec;
        }
    }
}
