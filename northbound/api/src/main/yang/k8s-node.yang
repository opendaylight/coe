module k8s-node {
    namespace "urn:opendaylight:coe:northbound:k8s-node";
    prefix "coe";

    revision 2017-08-29 {
        description "Initial revision";
    }

    import ietf-inet-types {
        prefix inet;
        revision-date "2013-07-15";
    }

    import ietf-yang-types {
        prefix yang;
        revision-date "2013-07-15";
    }

    organization "OpenDaylight COE Group";

    contact "COE Developers <coe-dev@lists.opendaylight.org>";

    container k8s-nodes-info {
        description
            "Kubernetes Nodes information";

        leaf id {
            description "Kubernetes node's data tree ID";
            type string;
        }
        list k8s-nodes {
            description "List of Kubernetes nodes.";

            key "uid";
            leaf uid {
                type yang:uuid;
                description "UUID representing the K8s node.";
            }
            leaf host-name {
                type string;
                description "The hostname as reported by the node’s kernel.";
            }
            leaf external-ip-address {
                type inet:ip-address;
                description "The IP address of the node that is externally routable.";
            }
            leaf internal-ip-address {
                type inet:ip-address;
                description "The IP address of the node that is routable only within the k8s cluster.
                    We assume that this IP address is reachable by OpenDaylight and it will be used to
                    set the default configurations.";
            }
            leaf pod-cidr {
                type string;
                description "PodCIDR represents the pod IP range assigned to the node.";
            }
        }
    }
}
